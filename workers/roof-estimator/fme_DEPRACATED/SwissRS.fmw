FME workspace SwissRS.fmw

Creator
    GEOMTYPE = Geometry Object
    NUM = 1
    CREATED -> FeatureReader [INITIATOR]
Note: Raster
FeatureReader
    ATTRIBUTES = GEOTIFF,datatype
    ATTR_ACCUM_MODE = Only Use Result
    CLIP_TO_ENVELOPE = NO
    COMBINE_GEOM = Use Result
    DATASET = D:\SwissRS\SWISSIMAGE-RS_10cm_Example.tif
    FORMAT = GEOTIFF
    GEOMETRY_TYPES = GEOTIFF,""",fme_raster"""
    GEOTIFF_APPLY_GCPS = NO
    GEOTIFF_FEATURE_TYPE_NAME = FORMAT_NAME
    GEOTIFF_IGNORE_RASTER_TYPE_KEY = No
    GEOTIFF_LENIENT_READ = Yes
    GEOTIFF_NATIVELY_HANDLED_WEBSERVICES = s3connector,azurestorage,google-cloud-storage
    GEOTIFF_PREFER_FILE_CS_UNITS = Yes
    GEOTIFF_READER_META_ATTRIBUTES = fme_dataset fme_basename
    GEOTIFF_READ_OFFSETS_IN_CS_UNITS = No
    GEOTIFF_SCALE_COLOR_TO_STANDARD_BIT_DEPTH = NO
    GEOTIFF_USE_SEARCH_ENVELOPE = NO
    INITIATOR_FIRST_OUTPUT = default
    INTERACT = NONE
    ORDER_RESULTS = No
    OUTPUT_ADD_SCHEMA_ATTRIBUTES = NO
    OUTPUT_FEATURES_DISPLAY = Schema and Data Features
    GEOTIFF -> FeatureReader_2 [INITIATOR]
    GEOTIFF -> CoordinateSystemSetter
Note: LV95
CoordinateSystemSetter
    COORDSYS = CH1903Plus_1.LV95/01
    -> RasterSelector
RasterSelector
    BAND_LIST = 0:;1:
    SELECTION_MODE_LOOKUP = USER
    SELECTION_MODE = Band and Palette List
    -> RasterExpressionEvaluator [A]
RasterExpressionEvaluator
    EXPRESSION_LIST = REAL64 if((A[0] + A[1]) == 0, -9999, (A[0] - A[1]) / (A[0] + A[1]))
    MODE = One Raster
    RESULT -> Clipper [CANDIDATE]
Note: Swisstopo 3D Buildings
FeatureReader_2
    ATTR_ACCUM_MODE = Only Use Result
    CLIP_TO_ENVELOPE = NO
    COMBINE_GEOM = Use Result
    DATASET = D:\swissbuildings3d_3_0_2025_2056_5728\SWISSBUILDINGS3D_3_0.gdb
    FORMAT = GEODATABASE_FILE
    GEODATABASE_FILE_ALIAS_MODE = NONE
    GEODATABASE_FILE_CACHE_MULTIPATCH_TEXTURES = yes
    GEODATABASE_FILE_CHECK_SIMPLE_GEOM = no
    GEODATABASE_FILE_CREATE_FEATURE_TABLES_FROM_DATA = Yes
    GEODATABASE_FILE_DISABLE_FEATURE_DATASET_ATTRIBUTE = Yes
    GEODATABASE_FILE_FEATURE_READ_MODE = Features
    GEODATABASE_FILE_IGNORE_NETWORK_INFO = yes
    GEODATABASE_FILE_IGNORE_RELATIONSHIP_INFO = yes
    GEODATABASE_FILE_MERGE_FEAT_LINKED_ANNOS = no
    GEODATABASE_FILE_QUERY_FEATURE_TYPES_FOR_MERGE_FILTERS = Yes
    GEODATABASE_FILE_READ_THREE_POINT_ARCS = no
    GEODATABASE_FILE_REMOVE_FEATURE_DATASET = NO
    GEODATABASE_FILE_RESOLVE_DOMAINS = no
    GEODATABASE_FILE_RESOLVE_SUBTYPE_NAMES = yes
    GEODATABASE_FILE_SIMPLE_DONUT_GEOMETRY = no
    GEODATABASE_FILE_SPLIT_COMPLEX_ANNOS = no
    GEODATABASE_FILE_SPLIT_COMPLEX_EDGES = no
    GEODATABASE_FILE_SPLIT_MULTI_PART_ANNOS = no
    GEODATABASE_FILE_STRIP_GUID_GLOBALID_BRACES = no
    GEODATABASE_FILE_TRANSLATE_SPATIAL_DATA_ONLY = no
    GEODATABASE_FILE_USE_SEARCH_ENVELOPE = NO
    INITIATOR_FIRST_OUTPUT = default
    INTERACT = CONTAINS
    MAX_FEATURES = 100
    ORDER_RESULTS = No
    OUTPUT_ADD_SCHEMA_ATTRIBUTES = NO
    OUTPUT_FEATURES_DISPLAY = Schema and Data Features
    <OTHER> -> CoordinateSystemSetter_2
Note: LV95
CoordinateSystemSetter_2
    COORDSYS = CH1903Plus_1.LV95/01
    -> SurfaceFootprintReplacer
SurfaceFootprintReplacer
    OFFSET_Z_LOOKUP = 0
    SHADOW_TYPE = OVERHEAD
    OFFSET_Z = 0
    SHADOW_MODE = Overhead Shadow
    FOOTPRINT -> Clipper [CLIPPER]
Clipper
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> PythonCaller
PythonCaller
    PYTHONSOURCE:
      # FME PythonCaller Script: Green Roof Statistics from NDVI raster
      # Input: Single-band NDVI raster (output from RasterExpressionEvaluator)
      # Expression used: (A[0] - A[1]) / (A[0] + A[1])
      # Output: Green roof statistics

      import fmeobjects
      import numpy as np
      import traceback

      # Configuration
      NDVI_THRESHOLD = 0.25  # Threshold for "green" classification

      class FeatureProcessor(object):

          def __init__(self):
              pass

          def input(self, feature):
              debug_info = []

              try:
                  debug_info.append("Step 1: Get raster")
                  geom = feature.getGeometry()

                  if geom is None or not isinstance(geom, fmeobjects.FMERaster):
                      self._set_error(feature, debug_info, "Not a raster")
                      return

                  raster = geom

                  # Get dimensions
                  props = raster.getProperties()
                  num_rows = props.getNumRows()
                  num_cols = props.getNumCols()
                  num_bands = raster.getNumBands()
                  debug_info.append(f"{num_rows}x{num_cols}, {num_bands} band(s)")

                  # Calculate pixel area from bounds
                  debug_info.append("Step 2: Pixel area")
                  try:
                      bbox = raster.boundingBox()
                      pixel_width = (bbox[1][0] - bbox[0][0]) / num_cols
                      pixel_height = (bbox[1][1] - bbox[0][1]) / num_rows
                      pixel_area = abs(pixel_width * pixel_height)
                      debug_info.append(f"{pixel_area:.4f} m2/pixel")
                  except:
                      pixel_area = 0.01  # Default 10cm resolution
                      debug_info.append("Using default 0.01 m2")

                  # Get NDVI band (band 0)
                  debug_info.append("Step 3: Get NDVI data")
                  band = raster.getBand(0)
                  band_props = band.getProperties()
                  interp = band_props.getInterpretation()
                  debug_info.append(f"Interp: {interp}")

                  # Try Real64 tile first (NDVI output), then Real32
                  tile = None
                  data = None

                  for tile_class in [fmeobjects.FMEReal64Tile, fmeobjects.FMEReal32Tile]:
                      try:
                          tile = tile_class(num_rows, num_cols)
                          tile = band.getTile(0, 0, tile)
                          data = tile.getData()
                          debug_info.append(f"Got data via {tile_class.__name__}")
                          break
                      except Exception as e:
                          debug_info.append(f"{tile_class.__name__} failed")
                          continue

                  if data is None:
                      self._set_error(feature, debug_info, "Could not read NDVI tile")
                      return

                  # Convert to numpy
                  debug_info.append("Step 4: Calculate stats")
                  ndvi = np.array(data, dtype=np.float64)
                  debug_info.append(f"Shape: {ndvi.shape}")
                  debug_info.append(f"Range: {ndvi.min():.3f} to {ndvi.max():.3f}")

                  # Filter valid NDVI values (-1 to 1 range, exclude nodata)
                  valid_mask = (ndvi >= -1) & (ndvi <= 1) & ~np.isnan(ndvi)
                  valid_ndvi = ndvi[valid_mask]
                  debug_info.append(f"Valid pixels: {len(valid_ndvi)}")

                  if len(valid_ndvi) == 0:
                      self._set_error(feature, debug_info, "No valid NDVI values")
                      return

                  # Calculate statistics
                  ndvi_avg = float(np.mean(valid_ndvi))
                  ndvi_min = float(np.min(valid_ndvi))
                  ndvi_max = float(np.max(valid_ndvi))

                  green_pixels = int(np.sum(valid_ndvi > NDVI_THRESHOLD))
                  total_pixels = len(valid_ndvi)
                  green_area_m2 = green_pixels * pixel_area
                  green_percentage = (green_pixels / total_pixels) * 100

                  # Classification
                  is_green_roof = 'Yes' if (green_percentage >= 30 and ndvi_avg > 0.15) else 'No'

                  debug_info.append(f"NDVI avg: {ndvi_avg:.3f}")
                  debug_info.append(f"Green: {green_percentage:.1f}% ({green_area_m2:.1f} m2)")
                  debug_info.append(f"Result: {is_green_roof}")

                  # Set attributes
                  feature.setAttribute('_ndvi_avg', round(ndvi_avg, 4))
                  feature.setAttribute('_ndvi_min', round(ndvi_min, 4))
                  feature.setAttribute('_ndvi_max', round(ndvi_max, 4))
                  feature.setAttribute('_is_green_roof', is_green_roof)
                  feature.setAttribute('_green_area_m2', round(green_area_m2, 2))
                  feature.setAttribute('_green_percentage', round(green_percentage, 2))
                  feature.setAttribute('_green_pixels', green_pixels)
                  feature.setAttribute('_total_pixels', total_pixels)
                  feature.setAttribute('_pixel_area_m2', round(pixel_area, 6))
                  debug_info.append("SUCCESS")

              except Exception as e:
                  debug_info.append(f"ERROR: {str(e)}")
                  self._set_error(feature, debug_info, str(e))
                  return

              feature.setAttribute('_debug', ' <pipe> '.join(debug_info))
              self.pyoutput(feature)

          def _set_error(self, feature, debug_info, msg):
              feature.setAttribute('_is_green_roof', 'Error')
              feature.setAttribute('_error_message', msg)
              feature.setAttribute('_debug', ' <pipe> '.join(debug_info))
              self.pyoutput(feature)

          def close(self):
              pass
    PYTHONSYMBOL = FeatureProcessor
    -> AttributeManager
AttributeManager
    USER_EXPOSED_ATTRIBUTES = _debug,_green_area_m2,_green_percentage,_green_pixels,_is_green_roof,_ndvi_avg,_ndvi_max,_ndvi_min,_pixel_area_m2,_total_pixels,geotiff_byte_order,geotiff_compression_method,geotiff_interleaving_type
    -> FeatureWriter [Output]
FeatureWriter
    CSV2_COORDINATE_SYSTEM_GRANULARITY = FEATURE_TYPE
    CSV2_DELIMITER = ,
    CSV2_ENCODING = UTF-8
    CSV2_EXISTING_FILE_HANDLING = Yes
    CSV2_EXTENSION = csv
    CSV2_FIELD_QUALIFIER_CHARACTER = "
    CSV2_FIELD_QUALIFIER_ESCAPE_CHARACTER = "
    CSV2_QUALIFY_FIELD_NAMES = if_needed
    CSV2_QUALIFY_FIELD_VALUES = if_needed
    CSV2_ROW_TERMINATION = System
    CSV2_TREAT_EMBEDDED_FIELD_QUALIFIERS_AS_UNSAFE = Yes
    CSV2_WRITE_BOM_FOR_UNICODE = Yes
    CSV2_WRITE_FIELD_NAMES = firstrow
    CSV2_WRITE_SCHEMA_FILE = NO
    DATASET = $(FME_MF_DIR_ENCODED)output
    DATASET_ATTR = _dataset
    FEATURE_TYPE_LIST_ATTR = _feature_types
    FORMAT = CSV2
    TOTAL_FEATURES_WRITTEN_ATTR = _total_features_written
